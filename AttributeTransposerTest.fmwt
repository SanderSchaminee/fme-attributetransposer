FME workspace AttributeTransposerTest.fmwt
Title: AttributeTransposerTest

Parameters:
- SourceDataset_XLSXR = $(FME_MF_DIR)1/Desktop/test.xlsx   # Source Microsoft Excel File(s)

Readers:
- XLSXR_1: XLSXR from $(SourceDataset_XLSXR)

Sheet 1 (reader XLSXR_1)
    attributes: Kriterie char(4), Testparameter char(5), Verdi 1 char(6), Verdi 2 char(6), Verdi 3 char(9), Verdi 2.5 char(6)
    -> AttributeTransposer
AttributeTransposer
    ROW_ATTR = Verdi 1 Verdi 3 Kriterie
    COL_ATTR = Testparameter
    -> StatisticsCalculator
    -> Sampler
Sampler
    RATE = 1
    SAMPLE_MODE = No
    SAMPLE_TYPE_LONG = First N Features
    SAMPLED -> AttributeExposer
AttributeExposer
    ATTR_LIST = 0,BLÄ,PROD,UNIK,Untitled,Untitled(1)
    -> Tester_2
Tester_2
    TEST_CLAUSE:
      TEST @Value(0) = 35634
      TEST @Value(BLÄ) = 11
      TEST @Value(PROD) = 1
      TEST @Value(Testparameter) = Verdi 1
      TEST @Value(UNIK) = En
      TEST @Value(Untitled) = reff
      TEST @Value(Untitled(1)) = 3gr
    BOOL_OP = AND
    TEST_MODE = Automatic
    TEST_DESCRIPTION = ""
    FAILED -> Terminator_2
Terminator_2
    MESSAGE = Result contains incorrect values
StatisticsCalculator
    PREPEND_ATTR_NAME_CHOICE = For multiple results only
    COUNT_ATTR = _count
    STATS_ATTRS = Testparameter
    COMPUTE_HISTOGRAM = NO
    SUMMARY -> Tester
Tester
    TEST_CLAUSE = TEST @Value(_count) = 3
    BOOL_OP = OR
    TEST_MODE = Automatic
    TEST_DESCRIPTION = ""
    FAILED -> Terminator
Terminator
    MESSAGE = Result should consist of 3 features
